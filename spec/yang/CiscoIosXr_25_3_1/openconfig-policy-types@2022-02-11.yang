module openconfig-policy-types {
  yang-version 1;
  namespace "http://openconfig.net/yang/policy-types";
  prefix oc-pol-types;

  revision "2022-02-11" {
    description
      "Schema slice containing the routing protocol identities referenced by
       the IOS XR 25.3.1 OpenConfig network-instance state used by flapmusik.";
  }

  identity INSTALL_PROTOCOL_TYPE {
    description
      "Base identity for protocols that may install routes.";
  }

  identity BGP {
    base INSTALL_PROTOCOL_TYPE;
    description "Border Gateway Protocol.";
  }
}
